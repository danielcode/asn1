TestModel DEFINITIONS ::= BEGIN -- Module parameters preamble
  SimpleSequence ::= SEQUENCE {
    simpleInt    INTEGER,
    simpleInt2   INTEGER,
    simpleString IA5String,
    simpleReal   REAL,
    simpleBool   BOOLEAN,
    simpleNull   NULL,
	simpleOptInt INTEGER OPTIONAL,
    optNull      NULL OPTIONAL -- Hardly simple
  }

  TestType  ::= INTEGER
  Test2Type ::= TestType
  Test3Type ::= Test2Type
  RealTest  ::= REAL
  BoolTest  ::= BOOLEAN
  NullTest  ::= NULL
  BmpString ::= BMPString
  Iso646String   ::= ISO646String
  -- Graphicstring    ::= GraphicString
  -- Generalstring    ::= GeneralString
  Numericstring    ::= NumericString
  Objectdescriptor ::= ObjectDescriptor
  ObjectIdentifier ::= OBJECT IDENTIFIER
  OctetString      ::= OCTET STRING
  Printablestring  ::= PrintableString
  Relativeoid      ::= RELATIVE-OID
  -- T61string        ::= T61String
  Teletexstring    ::= TeletexString
  UtcTime          ::= UTCTime
  Generalizedtime  ::= GeneralizedTime
  Universalstring  ::= UniversalString
  -- Videotexstring   ::= VideotexString
  Visiblestring    ::= VisibleString
  Any              ::= ANY

  BitString ::= BIT STRING

  TestChoice ::= CHOICE {
    int1 [0] INTEGER,
    int2 [1] INTEGER
  }

  TestIntSequence ::= SEQUENCE OF INTEGER

  TestEnumerated ::= ENUMERATED {
    one,
    two,
    three
  }

  TestNested ::= SEQUENCE {
    one SimpleSequence,
    two TestType
  }

  TestSequence ::= SEQUENCE {
    str     UTF8String,
    testVar TestType
  }

  TestSequenceOf ::= SEQUENCE OF TestSequence

  TestSet ::= SET {
    testSequence TestSequence,
    num          Test2Type
  }

  TestSetOf ::= SET OF TestSequence

  AnonSequence ::= SEQUENCE {
    sequence1 SEQUENCE {
      sequence2 SEQUENCE {
        sequence3 TestSequence,
        level3 INTEGER
      },
      level2 TestType
    },
    level1 Test2Type,
    testSequence TestSequence
  }

  RefTest ::= SEQUENCE {
    sequence3 TestSequence
  }

  DerivedAnonSequence ::= AnonSequence

  String1 ::= IA5String
  String2 ::= UTF8String

  RecursiveSequence ::= SEQUENCE {
    anonSequence      AnonSequence,
    recursiveSequence RecursiveSequence
  }

END
